--******************************************************************************
-- Copyright (c) 2000-2019 Ericsson Telecom AB
-- All rights reserved. This program and the accompanying materials
-- are made available under the terms of the Eclipse Public License v1.0
-- which accompanies this distribution, and is available at
-- http://www.eclipse.org/legal/epl-v10.html
--
-- Contributors:
--   Gabor Szalai - initial implementation and initial documentation
--*****************************************************************************/
--
--  File:               JSON_Generic_Null_Def.asn
--  Description:	      Generic type definition for JSON
--  Rev:                R1A
--  Prodnr:             CNL 113 899
--///////////////////////////////////////////// 
JSON-Generic-Null-Def
DEFINITIONS ::=  BEGIN
  
  IMPORTS;
  
  JSON-null-type ::= NULL

END
